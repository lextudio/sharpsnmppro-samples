TEST-MIB DEFINITIONS ::= BEGIN

IMPORTS
    OBJECT-TYPE,
    enterprises,
    NetworkAddress
	    FROM RFC1155-SMI;

mytest OBJECT IDENTIFIER ::= { enterprises 9999 }

testEntity14 -- test -- OBJECT-TYPE
    SYNTAX      NetworkAddress
    MAX-ACCESS  read-only
    STATUS      current
    DESCRIPTION
            "A textual description of the entity.  This value should
            include the full name and version identification of
            the system's hardware type, software operating-system,
            and networking software."
    ::= { mytest 14 }

END
